FME workspace DubbeleBomen_inspectieBestanden_backup.fmw

Parameters:
- SourceDataset_WFS = https://opendata.apps.mow.vlaanderen.be/opendata-geoserver/awv/wfs   # Source WFS (Web Feature Service) URL
- OUTPUT_FOLDER = C:\Users\DriesVerdoodtNordend\Downloads\output_20240919   # Select a folder
- TE_LINKEN_WEGSEGMENTEN = 1   # Link Boom en Wegsegment: max. aantal wegsegmenten
- MAX_BUFFER_BOOM_WEG = 100   # Link Boom en Wegsegment: max. bufferafstand (meter)
- MAX_BUFFER_BOOM_BOOM = 1   # Link Boom en Boom: max. bufferafstand (meter)
- DestDataset_XLSXW_3 = $(OUTPUT_FOLDER)\_dubbele_bomen_samenvatting.xlsx   # Destination Microsoft Excel File
- SourceDataset_SHAPEFILE = C:\DATA\AWV\GRB\Refprv.shp   # Source Esri Shapefile(s)
- TIMESTAMP:   # Timestamp
      from datetime import datetime
      return datetime.now().strftime('%Y%m%d')
- COOKIE = _hjSessionUser_1413636=eyJpZCI6IjQ1OTRlODY3LTg5NmItNTk4Yy1hZGM0LWY1MDg2ZGQ3YmVkMCIsImNyZWF0ZWQiOjE3MTMyNjUwODM3MjksImV4aXN0aW5nIjp0cnVlfQ==; _ga=GA1.1.220652939.1712582701; vo-taalkeuze=NL; _ga_KK7F9Y5Z4P=GS1.1.1725608638.32.1.1725609028.0.0.0; _ga_GR51QK0425=GS1.1.1725892656.6.1.1725896180.0.0.0; _ga_G7W38XJN8R=GS1.1.1726067286.50.0.1726067286.0.0.0; VOGANONUSER=rB8da2byW+E7kgAjfqpDAg==; acm-awv=ec25605531f44789b712bab2d709f3b9; _ga_2XTMG0FZW0=GS1.1.1727165526.428.1.1727165636.0.0.0   # Cookie

Readers:
- WFS_1: WFS from $(SourceDataset_WFS) in EPSG:31370
- XLSXR_1: XLSXR from $(FME_MF_DIR)DA-2024-24026_export.xlsx
- SHAPEFILE_1: SHAPEFILE from $(SourceDataset_SHAPEFILE) in EPSG:31370

Note: Dries Verdoodt / 13.09.2024 / Voorbereiding inspectiefiches van de dubbele bomen langs ieder wegsegment. / Schrijf een bestand weg per weg (beheersegment ident2). / Ieder bestand lijst alle bomen langsheen de weg in oplopende volgorde volgens de kilometerpaal referenties en de afstand tot deze kilometerpaal. / De afstand is opnieuw berekend en stemt niet per se overeen met de info uit ELISA-Infra. / Iedere boom heeft en group.id indien ze gegroepeerd staan. Ontbreekt de groep id, dan staat die boom geïsoleerd (zoals het hoort). / Toevoegen of er een Controlefiche bestaat van de boom.
Note: De afgeleide locatie ( / referentiepunt.wegnummer en referentiepunt.opschrift) uit de data halen, en niet zelf berekenen.
Note: DEV: N364
Tester
    BOOL_OP = OR
    TEST_CLAUSE:
      CASE_INSENSITIVE_TEST @Value(referentiepunt.Wegnummer) BEGINS_WITH N364
      CASE_INSENSITIVE_TEST @Value(referentiepunt.Wegnummer) BEGINS_WITH N008000
    TEST_MODE = CASE_INSENSITIVE_TEST
    PASSED -> Sorter_2
    FAILED -> Sorter_2
Sorter_2
    SORT_PARM = referentiepunt.Wegnummer NATURAL ASCENDING referentiepunt.Opschrift NATURAL ASCENDING
    SORTED -> NeighborFinder_3 [CANDIDATE]
    SORTED -> NeighborFinder_3 [BASE]
ListExploder_4
    ATTR_ACCUM_MODE = Merge List Attributes
    ATTR_CONFLICT_RES = Use List Attribute Values
    INDEX_ATTR = _element_index
    LIST_ATTR = DubbeleBoom{}
    ELEMENTS -> AttributeKeeper_2
AttributeKeeper_2
    CREATE_BULK_MODE_FEATURES = NO
    KEEP_ATTRS = assetId.identificator,group.id,referentiepunt.Opschrift,referentiepunt.Wegnummer,referentiepunt.distance
    -> DuplicateFilter_2
Note: Behoud 1 unieke boom (assetId.identificator) per wegsegment (referentiepunt.Wegnummer) / Group by: / - assetId.identificator / - referentiepunt.Wegnummer
DuplicateFilter_2
    INPUT_ORDERED_CHOICE = No
    KEYATTR = assetId.identificator referentiepunt.Wegnummer
    UNIQUE -> FeatureMerger [SUPPLIER]
Note: NeighborFinder : MatchedBase
Junction_3
    -> FeatureMerger [REQUESTOR]
NeighborFinder_2
    CANDIDATES_FIRST = No
    CLOSE_LIST_ATTRS_TO_INCLUDE = assetId.identificator
    CLOSE_LIST_ATTRS_TO_INCLUDE_MODE = Selected Attributes
    CLOSE_LIST_NAME = DubbeleBoom
    INSERT_VERTEX = No
    MAX = $(MAX_BUFFER_BOOM_BOOM)
    MEASURES_FROM_CANDIDATE = Yes
    MEASURE_TYPE = Continuous
    MODE = Bases and Candidates
    TREAT_POLYGON_AS = Lines
    MATCHED -> ListElementCounter_2
ListElementCounter_2
    CNT_ATTR = _element_count
    LIST_NAME = DubbeleBoom{}
    -> TestFilter_4
TestFilter_4
    DEFAULT_VALUE = <UNFILTERED>
    PASSED_TEST_GROUP_OUTPUT = FIRST
    TEST_LIST = "BOOL_OP,OR,COMPOSITE_TEST,""""""1"""""",TEST_CLAUSE,TEST @Value(_element_count) >= 2",Dubbele boom
    Dubbele boom -> AttributeCreator_3
    <UNFILTERED> -> AttributeCreator_2
Note: group.id = -99
AttributeCreator_3
    ATTR_TABLE = SET_TO group.id (varchar(14)) = -99
    -> ListExploder_2
ListExploder_2
    ATTR_ACCUM_MODE = Merge List Attributes
    ATTR_CONFLICT_RES = Use List Attribute Values
    INDEX_ATTR = _element_index
    LIST_ATTR = DubbeleBoom{}
    ELEMENTS -> AttributeKeeper_3
AttributeKeeper_3
    CREATE_BULK_MODE_FEATURES = NO
    KEEP_ATTRS = assetId.identificator,group.id,referentiepunt.Wegnummer
    -> DuplicateFilter_3
Note: Behoud 1 unieke boom (assetId.identificator) per wegsegment (referentiepunt.Wegnummer) / Group by: / - assetId.identificator / - referentiepunt.Wegnummer
DuplicateFilter_3
    INPUT_ORDERED_CHOICE = No
    KEYATTR = assetId.identificator referentiepunt.Wegnummer
    UNIQUE -> FeatureMerger [SUPPLIER]
FeatureMerger
    ATTR_ACCUM_MODE = Merge Supplier
    ATTR_CONFLICT_RES = Use Requestor
    IGNORE_NULLS = No
    JOIN_KEYS = @Value(assetId.identificator) @Value(assetId.identificator) AUTO
    MERGE_TYPE = Attributes Only
    PROCESS_DUPS = NO
    REJECT_NULL_MISSING_KEYS = No
    SUPPLIERS_FIRST = No
    MERGED -> PythonCaller
    UNMERGED_REQUESTOR -> PythonCaller
Note: Calculate ident2
PythonCaller
    NEW_ATTRIBUTES = ident8 buffer ident2 buffer
    PYTHONSOURCE:
      # David Vlaminck
      # 16.09.2024
      import fme
      import fmeobjects


      class FeatureProcessor(object):
          """

          """
          def __init__(self):
              """
              """
              pass

          @classmethod
          def convert(cls, ident8: str) -> str | None:
              if not isinstance(ident8, str) or len(ident8) != 8:
                  return ident8
              if not ident8[0].isalpha() or not ident8[1:4].isdigit():
                  return ident8
              number = ident8[1:4].lstrip('0') or '0'
              suffix = int(ident8[5:7])
              if ident8[4] == '9' and suffix >= 1 and suffix <= 26:
                  return f'{ident8[0]}{number}{chr(96 + suffix)}'
              return f'{ident8[0]}{number}'

          def input(self, feature: fmeobjects.FMEFeature):
              """
              """
              ident8 = feature.getAttribute('referentiepunt.Wegnummer')
              ident2 = self.convert(ident8)
              # print(f'Ident8: {ident8} and Ident2: {ident2}')

              feature.setAttribute('ident8', ident8)
              feature.setAttribute('ident2', ident2)

              self.pyoutput(feature)

          def close(self):
              pass
    PYTHONSYMBOL = FeatureProcessor
    -> ControleFiche
ControleFiche
    ASSETID.IDENTIFICATOR = @Value(assetId.identificator)
    COOKIE = $(COOKIE)
    -> AttributeManager
AttributeManager
    ATTR_TABLE:
      REMOVE _distance (real64)
      REMOVE _angle (real64)
      REMOVE _candidate_angle (real64)
      REMOVE _candidate_label_angle (real64)
      REMOVE _closest_candidate_x (real64)
      REMOVE _closest_candidate_y (real64)
      REMOVE _closest_base_x (real64)
      REMOVE _closest_base_y (real64)
      RENAME_SET_VALUE ident8 > referentiepunt.ident8 (buffer)
      RENAME_SET_VALUE ident2 > referentiepunt.ident2 (buffer)
      REMOVE referentiepunt.Bijkomende_Wegnummers (buffer)
      RENAME_SET_VALUE referentiepunt.distance > referentiepunt.afstand (real64)
      REMOVE referentiepunt.angle (real64)
      REMOVE referentiepunt.candidate_angle (real64)
      REMOVE referentiepunt.candidate_label_angle (real64)
      REMOVE referentiepunt.closest_candidate_x (real64)
      REMOVE referentiepunt.closest_candidate_y (real64)
      REMOVE referentiepunt.closest_base_x (real64)
      REMOVE referentiepunt.closest_base_y (real64)
      REMOVE referentiepunt.counter (uint32)
      SET_TO isActief.voorstel (varchar(200)) = @Value(isActief)
    -> Sorter
Note: kilometerpalen / oplopend / referentiepunt.Opschrift / refernetiepunt.afstand / group.id
Sorter
    GROUP_BY = referentiepunt.ident2
    SORT_PARM = group.id NATURAL ASCENDING referentiepunt.Opschrift NATURAL ASCENDING referentiepunt.afstand NATURAL ASCENDING
    SORTED -> StatisticsCalculator
    SORTED -> AttributeManager_3
Note: group.id = <null>
AttributeCreator_2
    ATTR_TABLE = SET_TO group.id (varchar(14)) = FME_NULL_VALUE

Bookmark: [Excel] DAVIE Download
Note: Bomen / Vlaanderen / DAVIE-Conform
Boom (reader XLSXR_1)
    attributes: typeURI char(59), assetId.identificator char(56), aanleg string, aanleg.heeftBoomplaat string, aanleg.heeftWortelgeleidingwortelwering string, aanleg.plantmaatOmtrek string, aanleg.verankering string, aanleg.verankeringstype string, aanleg.vormAanlevering string, aanleg.wortelAanplant string, assetId.toegekendDoor char(3), boomspiegel[] char(16), datumOprichtingObject date, eindbeeld char(21), geschatteKlassePlantjaar char(9), groeifase char(13), heeftBoomrooster boolean, heeftLuchtleiding boolean, hoogte char(19), isActief boolean, isVerplant string, naam number(6,0), niveau number(4,1), notitie char(116), soortnaam.soortnaamNederlands char(52), soortnaam.soortnaamWetenschappelijk char(40), soortnaam.wetenschappelijkeSoortnaam char(36), takvrijeStamlengte number(3,1), toestand char(10), geometry char(37)
    -> TestFilter
TestFilter
    DEFAULT_VALUE = isActief False
    PASSED_TEST_GROUP_OUTPUT = FIRST
    TEST_LIST = "BOOL_OP,OR,COMPOSITE_TEST,""""""1"""""",TEST_CLAUSE,TEST @Value(isActief) = true",isActief True
    isActief True -> GeometryReplacer
HeeftBetrokkene (reader XLSXR_1) [off]
    attributes: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

Bookmark: Replace geometry
GeometryReplacer
    KIND_LONG = OGC Well Known Text
    OGC_WKT_PRECISION_DISPLAY = 64-bit
    REMOVE_ATTRIBUTE = No
    SOURCE = @Value(geometry)
    -> CoordinateSystemSetter
    <REJECTED> -> Junction_6
CoordinateSystemSetter
    COORDSYS = EPSG:31370
    -> NeighborFinder [BASE]
Note: Boom zonder geometrie
Junction_6

Bookmark: [WFS] AWV
Beheersegmenten (reader WFS_1) [off]
    attributes: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
Referentiepunten (reader WFS_1)
    attributes: gml_parent_id xml_buffer, gml_parent_property xml_buffer, gml_id xml_buffer, Wegnummer xml_buffer, Wegnummer.xsi_nil xml_boolean, Bijkomende_Wegnummers xml_buffer, Bijkomende_Wegnummers.xsi_nil xml_boolean, Opschrift xml_real64, Opschrift.xsi_nil xml_boolean, Materiaal xml_buffer, Materiaal.xsi_nil xml_boolean, Opmerking xml_buffer, Opmerking.xsi_nil xml_boolean, Begindatum xml_buffer, Begindatum.xsi_nil xml_boolean, Creatiedatum xml_buffer, Creatiedatum.xsi_nil xml_boolean, Opnamedatum xml_buffer, Opnamedatum.xsi_nil xml_boolean, Wijzigingsdatum xml_buffer, Wijzigingsdatum.xsi_nil xml_boolean, geometry xml_geometry
    -> NeighborFinder [CANDIDATE]

Bookmark: Toewijzen informatie van het Wegsegment aan de Boom
Note: Candidates first: Yes (performance) / Maak een lijst en voeg de eerste twee, meest nabijgelegen, matches toe. Het eerste lijst element is het kortst bijzijnde.
NeighborFinder
    CANDIDATES_FIRST = Yes
    CLOSE_LIST_ATTRS_TO_INCLUDE = Bijkomende_Wegnummers Opschrift Wegnummer
    CLOSE_LIST_ATTRS_TO_INCLUDE_MODE = Selected Attributes
    CLOSE_LIST_NAME = Referentiepunten
    INSERT_VERTEX = No
    K = $(TE_LINKEN_WEGSEGMENTEN)
    MAX = $(MAX_BUFFER_BOOM_WEG)
    MEASURES_FROM_CANDIDATE = Yes
    MEASURE_TYPE = Continuous
    MODE = Bases and Candidates
    TREAT_POLYGON_AS = Lines
    MATCHED -> ListExploder
    UNMATCHED_BASE -> Junction
ListExploder
    ATTR_ACCUM_MODE = Prefix List Attributes
    INCOMING_PREFIX = referentiepunt.
    INDEX_ATTR = referentiepunt.counter
    LIST_ATTR = Referentiepunten{}
    ELEMENTS -> AttributeKeeper
    ELEMENTS -> Junction_2
Note: Attribute: assetId.identificator / List: <All>
AttributeKeeper
    CREATE_BULK_MODE_FEATURES = NO
    KEEP_ATTRS = assetId.identificator,referentiepunt.Opschrift,referentiepunt.Wegnummer,referentiepunt.distance
    -> Tester
Note: Boom mét wegnummer
Junction_2
    -> Junction_4
Note: Schrijf deze Bomen weg naar een apart bestand: Geen Wegsegment gevonden dat gekoppeld kan worden, maar de bomen moeten alsnog geïnspecteerd worden.
Junction
    -> AttributeCreator_4
Note: referentiepunt.Wegnummer = XXX
AttributeCreator_4
    ATTR_TABLE = SET_TO referentiepunt.Wegnummer (varchar(3)) = XXX
    -> NeighborFinder_2 [CANDIDATE]
    -> NeighborFinder_2 [BASE]
    -> Junction_5
Note: Boom zonder wegnummer
Junction_5
    -> Junction_4
Note: Wegschrijven naar Excel
Junction_4
    -> Junction_3

Bookmark: Toevoegen group.id
Note: Base en Candidate input poort zijn identiek. / Group by: referntiepunt.Wegnummer / Alle elementen van een groep zitten zo in de lijst. / De attributen van de feature worden overbodig, want deze zit mee in de lijst.
Note: Base en Candidate input poort zijn identiek. / Group by: referntiepunt.Wegnummer / Alle elementen van een groep zitten zo in de lijst. / De attributen van de feature worden overbodig, want deze zit mee in de lijst.
NeighborFinder_3
    CANDIDATES_FIRST = No
    CLOSE_LIST_ATTRS_TO_INCLUDE = assetId.identificator referentiepunt.Opschrift referentiepunt.Wegnummer
    CLOSE_LIST_ATTRS_TO_INCLUDE_MODE = Selected Attributes
    CLOSE_LIST_NAME = DubbeleBoom
    GROUP_BY = referentiepunt.Wegnummer
    INSERT_VERTEX = No
    MAX = $(MAX_BUFFER_BOOM_BOOM)
    MEASURES_FROM_CANDIDATE = Yes
    MEASURE_TYPE = Continuous
    MODE = Bases and Candidates
    TREAT_POLYGON_AS = Lines
    MATCHED -> ListElementCounter
ListElementCounter
    CNT_ATTR = _element_count
    LIST_NAME = DubbeleBoom{}
    -> TestFilter_3
TestFilter_3
    DEFAULT_VALUE = <UNFILTERED>
    PASSED_TEST_GROUP_OUTPUT = FIRST
    TEST_LIST = "BOOL_OP,OR,COMPOSITE_TEST,""""""1"""""",TEST_CLAUSE,TEST @Value(_element_count) >= 2",Dubbele boom
    Dubbele boom -> Counter_2
    <UNFILTERED> -> AttributeCreator
Note: Toekennen van een group.id, enkel voor de dubbele bomen. Voor alle records die uit minstens 2 lijst elementen bestaan.
Counter_2
    CNT_ATTR = group.id
    DOMAIN = counter
    SCOPE = Global
    START = 0
    -> ListExploder_4
Note: group.id = <null>
AttributeCreator
    ATTR_TABLE = SET_TO group.id (varchar(14)) = FME_NULL_VALUE

Bookmark: File per wegsegment
Note: Create fanout attribute _filename
AttributeManager_3
    ATTR_TABLE = SET_TO _filename (varchar(200)) = @Value(referentiepunt.ident2)_dubbeleBoom_$(TIMESTAMP).xlsx
    -> FeatureWriter [Output]
FeatureWriter
    DATASET = $(OUTPUT_FOLDER)/@Value(_filename)
    DATASET_ATTR = _dataset
    FEATURE_TYPE_LIST_ATTR = _feature_types
    FORMAT = XLSXW
    TOTAL_FEATURES_WRITTEN_ATTR = _total_features_written
    XLSXW_COORDINATE_SYSTEM_GRANULARITY = FEATURE
    XLSXW_CUSTOM_NUMBER_FORMATTING = ENABLE_NATIVE
    XLSXW_DESTINATION_DATASETTYPE_VALIDATION = Yes
    XLSXW_DROP_TABLE = No
    XLSXW_FIELD_NAMES_FORMATTING = YES
    XLSXW_FIELD_NAMES_OUT = Yes
    XLSXW_INSERT_IGNORE_DB_OP = Yes
    XLSXW_MULTIPLE_TEMPLATE_SHEETS = Yes
    XLSXW_OVERWRITE_FILE = Yes
    XLSXW_PROTECT_SHEET = NO
    XLSXW_RASTER_FORMAT = PNG
    XLSXW_REMOVE_UNCHANGED_TEMPLATE_SHEET = No
    XLSXW_STRICT_SCHEMA_ADDITIONAL_ATTRIBUTE_MATCHING = yes
    XLSXW_TRUNCATE_TABLE = No
    XLSXW_WRITER_MODE = Insert

Bookmark: Samenvatting
StatisticsCalculator
    ATTR_ACCUM_MODE = None
    CALCULATION_MODE = NUMERIC
    FEAT_STATS = group.id,NUMERIC_MODE,,,COUNT,,,,NUMERIC,,,,,,
    GROUP_BY = referentiepunt.ident2
    SUMMARY -> AttributeManager_2
AttributeManager_2
    ATTR_TABLE:
      RENAME_SET_VALUE group.id.numeric_count > aantal_dubbels (uint64)
      RENAME_SET_VALUE group.id.total_count > aantal_totaal (uint64)
      SET_TO vaststelling (varchar(200))
      SET_TO oplossing (varchar(200))
      SET_TO opmerking (varchar(200))
    -> Sorter_3
Sorter_3
    SORT_PARM = referentiepunt.ident2 NATURAL ASCENDING
    SORTED -> FeatureWriter_2 [Output]
FeatureWriter_2
    DATASET = $(DestDataset_XLSXW_3)
    DATASET_ATTR = _dataset
    FEATURE_TYPE_LIST_ATTR = _feature_types
    FORMAT = XLSXW
    TOTAL_FEATURES_WRITTEN_ATTR = _total_features_written
    XLSXW_COORDINATE_SYSTEM_GRANULARITY = FEATURE
    XLSXW_CUSTOM_NUMBER_FORMATTING = ENABLE_NATIVE
    XLSXW_DESTINATION_DATASETTYPE_VALIDATION = Yes
    XLSXW_DROP_TABLE = No
    XLSXW_FIELD_NAMES_FORMATTING = NO
    XLSXW_FIELD_NAMES_OUT = Yes
    XLSXW_INSERT_IGNORE_DB_OP = Yes
    XLSXW_MULTIPLE_TEMPLATE_SHEETS = Yes
    XLSXW_OVERWRITE_FILE = Yes
    XLSXW_PROTECT_SHEET = NO
    XLSXW_RASTER_FORMAT = PNG
    XLSXW_REMOVE_UNCHANGED_TEMPLATE_SHEET = No
    XLSXW_STRICT_SCHEMA_ADDITIONAL_ATTRIBUTE_MATCHING = yes
    XLSXW_TRUNCATE_TABLE = No
    XLSXW_WRITER_MODE = Insert

Bookmark: [ESRI Shape] Provincies
Note: OPTIONEEL: / Toekennen provincie
Refprv (reader SHAPEFILE_1) [off]
    attributes: OIDN number(15,0), UIDN number(15,0), TERRID long, NAAM varchar(64), NISCODE varchar(5), NUTS2 varchar(10), LENGTE double, OPPERVL double

Bookmark: [Excel]
Note: Fanout op basis van het wegsegment / Samenvatting van de aantallen per wegsegment

FME custom transformer ControleFiche
Toevoegen boolean attribuut "heeftControlefiche" voor iedere Boom o.b.v. een API-Call.

Parameters:
- ASSETID.IDENTIFICATOR = @Value(assetId.identificator)   # assetId.identificator
- COOKIE = _hjSessionUser_1413636=eyJpZCI6IjQ1OTRlODY3LTg5NmItNTk4Yy1hZGM0LWY1MDg2ZGQ3YmVkMCIsImNyZWF0ZWQiOjE3MTMyNjUwODM3MjksImV4aXN0aW5nIjp0cnVlfQ==; _ga=GA1.1.220652939.1712582701; vo-taalkeuze=NL; _ga_KK7F9Y5Z4P=GS1.1.1725608638.32.1.1725609028.0.0.0; _ga_GR51QK0425=GS1.1.1725892656.6.1.1725896180.0.0.0; _ga_G7W38XJN8R=GS1.1.1726067286.50.0.1726067286.0.0.0; VOGANONUSER=rB8dZGbqd/UyHwAabDlQAg==; acm-awv=97472f24145941358956b77fab54f2d1; _ga_2XTMG0FZW0=GS1.1.1726642387.413.1.1726642390.0.0.0   # Cookie

Input (input)
    -> Junction_5
Junction_5
    -> PythonCaller_3
    -> AttributeManager_5
AttributeManager_5
    ATTR_TABLE = SET_TO uuid (varchar(200)) = @Left(@Value(assetId.identificator), 36)
    -> FeatureMerger_2 [REQUESTOR]
Note: Groepeer de uuid's in een lijst van maximaal 100 assets. / Stuur iedere lijst van 100 assets naar de API request, zodat het aantal requests (verkeer) afneemt.
PythonCaller_3
    HIDE_ATTRIBUTES = assetId.identificator
    NEW_ATTRIBUTES = uuid_list buffer
    PYTHONSOURCE:
      import fme
      import fmeobjects


      class FeatureProcessor(object):
          """

          """

          def __init__(self):
              """
              """
              self.uuid_list = []


          def input(self, feature: fmeobjects.FMEFeature):
              """
              """
              uuid = feature.getAttribute('assetId.identificator')[:36]  # Slice the first 36 characters of the string
              self.uuid_list.append(uuid)

              #self.pyoutput(feature)

          def close(self):
              # Split into chunks of 1000 items
              chunks = [self.uuid_list[i:i + 100] for i in range(0, len(self.uuid_list), 100)]

              for chunk in chunks:
                  newFeature = fmeobjects.FMEFeature()
                  # Convert the list to a string, with elements separated by a comma and space
                  chunks_as_string = ', '.join(f'"{item}"' for item in chunk)
                  newFeature.setAttribute('uuid_list', chunks_as_string)
                  self.pyoutput(newFeature)
    PYTHONSYMBOL = FeatureProcessor
    -> AttributeCreator_5
Note: upload_body (payload)
AttributeCreator_5
    ATTR_TABLE:
      SET_TO upload_body (varchar(200)) = {
            "actiefFilter": true,
            "expandDepth": 1,
            "limit": 1000,
            "relatieTypesToExpand": [
                "e801b062-74e1-4b39-9401-163dd91d5494"
                ],
            "relatieTypesToReturn": [
                "e801b062-74e1-4b39-9401-163dd91d5494"
                ],
            "uuidsToExpand": [
                @Value(uuid_list)
            ],
            "uuidsToInclude": [
                @Value(uuid_list)
            ]
        }
    -> HTTPCaller
Note: API-Call: / Zoek alle assetsrelaties met als doeluuid een uuid van een boom met als relatietype "Bezoekt" / https://apps.mow.vlaanderen.be/eminfra/core/api/assets/graph / Copy the Cookie from a Browser
HTTPCaller
    CONNECTION_TIMEOUT_LENGTH = 60
    CUSTOM_HEADERS = Cookie;$(COOKIE)
    ERROR_ATTR = _error
    FOLLOW_REDIRECTS = FOLLOW_WITH_GET
    HTTP_METHOD = POST
    MAX_HTTP_VERSION = HTTP_2
    MAX_TRANSFERS_IN_PROGRESS = 25
    MINIMUM_ENCRYPTION_LEVEL = OS_DEFAULT
    REDIRECT_AUTH = ORIGINAL_DOMAIN_ONLY
    RESPONSE_TYPE = Attribute
    SPLIT_MULTIPART_DOWNLOADS = NO
    STATUS_CODE_ATTR = _http_status_code
    TARGET_ATTR = _response_body
    TARGET_ATTR_ENCODING = auto-detect
    TARGET_URL = https://apps.mow.vlaanderen.be/eminfra/core/api/assets/graph
    TRANSFER_TIMEOUT_LENGTH = 90
    UPLOAD_BODY = @Value(upload_body)
    UPLOAD_CONTENT_TYPE = JSON (application/json)
    UPLOAD_TYPE = Specify Upload Body
    USE_COOKIES = No
    VERIFY_SSL_CERTIFICATES = Yes
    -> JSONFragmenter_2
Note: Split the response in fragments (list) / Haal de "links" op tussen een boom en een controlefiche. / Splits op in fragmenten per / boom <-> controlefiche.
JSONFragmenter_2
    EXPLODE_FORMAT = JSON
    EXTRACT_ATTR = Yes
    JSON_ATTR = _response_body
    JSON_QUERY = json["links"][*]
    PREF_STRING = boom.links.
    READ_FROM_FILE = NO
    RECURSIVE = YES
    REJECT_EMPTY_LISTS = YES
    FRAGMENTS -> JSONExtractor
Note: bronuuid (ProefBoomToestand) / doeluuid (Boom)
JSONExtractor
    EXTRACT_QUERY_TABLE = bronuuid json["bronUuid"] doeluuid json["doelUuid"]
    JSON_DOCUMENT = @Value(_response_body)
    READ_FROM_FILE = NO
    EVALUATED -> StatisticsCalculator
Note: Bereken hoeveel controlefiches er per boom bestaan. / Meestal is dat er 1. Soms zijn het er (maximaal) 2, en dan is de info nagenoeg identiek.
StatisticsCalculator
    ATTR_ACCUM_MODE = None
    CALCULATION_MODE = NUMERIC
    FEAT_STATS = doeluuid,NUMERIC_MODE,,,COUNT,,,,,,,,,,
    GROUP_BY = doeluuid
    COMPLETE -> HTTPCaller_2
Note: Verbetering: kunnen meerdere controlefiches worden opgevraagd met 1 enkele Call? Eerst de id's groeperen en nadien de call lanceren.
Note: Haal de ControleFiche op van de boom / GET / https://apps.mow.vlaanderen.be/eminfra/core/api/otl/controlefiches/@Value(bronuuid)
HTTPCaller_2
    CONNECTION_TIMEOUT_LENGTH = 60
    CUSTOM_HEADERS = Cookie;$(COOKIE)
    ERROR_ATTR = _error
    FOLLOW_REDIRECTS = FOLLOW_WITH_GET
    HTTP_METHOD = GET
    MAX_HTTP_VERSION = HTTP_2
    MAX_TRANSFERS_IN_PROGRESS = 25
    MINIMUM_ENCRYPTION_LEVEL = OS_DEFAULT
    REDIRECT_AUTH = ORIGINAL_DOMAIN_ONLY
    RESPONSE_TYPE = Attribute
    SPLIT_MULTIPART_DOWNLOADS = NO
    STATUS_CODE_ATTR = _http_status_code
    TARGET_ATTR = _response_body
    TARGET_ATTR_ENCODING = auto-detect
    TARGET_URL = https://apps.mow.vlaanderen.be/eminfra/core/api/otl/controlefiches/@Value(bronuuid)
    TRANSFER_TIMEOUT_LENGTH = 90
    USE_COOKIES = No
    VERIFY_SSL_CERTIFICATES = Yes
    -> JSONFragmenter
Note: Splits het antwoord op in verschillende JSON fragmenten.
JSONFragmenter
    EXPLODE_FORMAT = JSON
    EXTRACT_ATTR = No
    JSON_ATTR = _response_body
    JSON_QUERY = json["@graph"][*]
    READ_FROM_FILE = NO
    REJECT_EMPTY_LISTS = YES
    FRAGMENTS -> JSONExtractor_4
Note: Algemeen / @type / @id
JSONExtractor_4
    EXTRACT_QUERY_TABLE = @type json["@type"] @id json["@id"]
    JSON_DOCUMENT = @Value(_response_body)
    READ_FROM_FILE = NO
    EVALUATED -> AttributeFilter
Note: Sommige delen van het antwoord van de API-call interesseren ons niet.
AttributeFilter
    ATTR_NAME = @type
    ATTR_VALUES = <Empty>,<Missing>,<Null>,<Unfiltered>,https://bz.data.wegenenverkeer.be/ns/aanleiding#Proef,https://bz.data.wegenenverkeer.be/ns/beheeractie#ProefBoomToestand,https://bz.data.wegenenverkeer.be/ns/controlefiche#ProefBoomToestand,https://bz.data.wegenenverkeer.be/ns/onderdeel#Bezoekt,https://bz.data.wegenenverkeer.be/ns/onderdeel#HeeftBeheeractie,https://bz.data.wegenenverkeer.be/ns/onderdeel#IsAanleiding,https://wegenenverkeer.data.vlaanderen.be/ns/onderdeel#Boom
    https://bz.data.wegenenverkeer.be/ns/beheeractie#ProefBoomToestand -> JSONExtractor_2
    https://bz.data.wegenenverkeer.be/ns/controlefiche#ProefBoomToestand -> JSONExtractor_3
    https://wegenenverkeer.data.vlaanderen.be/ns/onderdeel#Boom -> JSONExtractor_5
Note: Indien er 2 controlefiches zijn, hebben deze dezelfde waarde. Ze zijn 2 aan 2 gelijk.
Note: beheeractie#ProefBoomToestand
JSONExtractor_2
    EXTRACT_QUERY_TABLE = ProefBoomToestand.conditiewaarde json["bz:ProefBoomToestand.conditiewaarde"] ProefBoomToestand.gebreken json["bz:ProefBoomToestand.gebreken"] ProefBoomToestand.onderhoudstoestand json["bz:ProefBoomToestand.onderhoudstoestand"] ProefBoomToestand.plantwijzewaarde json["bz:ProefBoomToestand.plantwijzewaarde"] ProefBoomToestand.stamomtrek json["bz:ProefBoomToestand.stamomtrek"] ProefBoomToestand.standplaatswaarde json["bz:ProefBoomToestand.standplaatswaarde"]
    JSON_DOCUMENT = @Value(_response_body)
    READ_FROM_FILE = NO
    EVALUATED -> FeatureMerger [REQUESTOR]
Note: Indien er 2 controlefiches zijn, heeft de eigenschap "verstuurd op" voor de eerste record een waarde en voor de tweede record geen waarde. / De eerste record wordt gebruikt en de lege eigenschap genegeerd.
Note: controlefiche#ProefBoomToestand
JSONExtractor_3
    EXTRACT_QUERY_TABLE = Controlefiche.verstuurdOp json["bz:Controlefiche.verstuurdOp"]
    JSON_DOCUMENT = @Value(_response_body)
    READ_FROM_FILE = NO
    EVALUATED -> AttributeKeeper_2
AttributeKeeper_2
    CREATE_BULK_MODE_FEATURES = NO
    KEEP_ATTRS = doeluuid,Controlefiche.verstuurdOp
    -> FeatureMerger [SUPPLIER]
Note: Breng de info samen op basis van de eigenschap doeluuid
FeatureMerger
    ATTR_ACCUM_MODE = Merge Supplier
    ATTR_CONFLICT_RES = Use Requestor
    IGNORE_NULLS = No
    JOIN_KEYS = @Value(doeluuid) @Value(doeluuid) AUTO
    MERGE_TYPE = Attributes Only
    PROCESS_DUPS = NO
    REJECT_NULL_MISSING_KEYS = No
    SUPPLIERS_FIRST = No
    MERGED -> FeatureMerger_3 [REQUESTOR]
    <REJECTED> -> Logger
Logger
    LOG_FEATURE = LOG_ONLY
    MAXCOORDS = 20
    MAXFEATS = 20
    MESSAGE = Feature is:
    SEVERITY = INFO
Note: onderdeel#Boom / Extraheer de afgeleide weglocatie: / ident2 / ident8 / referentiepaalOpschrift / referentiepaalAfstand
JSONExtractor_5
    EXTRACT_QUERY_TABLE:
      Weglocatie.ident2 json["loc:Locatie.puntlocatie"]["loc:DtcPuntLocatie.weglocatie"]["loc:DtcWeglocatie.ident2"] Weglocatie.ident8 json["loc:Locatie.puntlocatie"]["loc:DtcPuntLocatie.weglocatie"]["loc:DtcWeglocatie.ident8"] Weglocatie.referentiepaalOpschrift json["loc:Locatie.puntlocatie"]["loc:DtcPuntLocatie.weglocatie"]["loc:DtcWeglocatie.referentiepaalOpschrift"]
       Weglocatie.referentiepaalAfstand json["loc:Locatie.puntlocatie"]["loc:DtcPuntLocatie.weglocatie"]["loc:DtcWeglocatie.referentiepaalAfstand"]
    JSON_DOCUMENT = @Value(_response_body)
    READ_FROM_FILE = NO
    EVALUATED -> AttributeKeeper
AttributeKeeper
    CREATE_BULK_MODE_FEATURES = NO
    KEEP_ATTRS = Weglocatie.ident2,Weglocatie.ident8,Weglocatie.referentiepaalAfstand,Weglocatie.referentiepaalOpschrift,doeluuid
    -> FeatureMerger_3 [SUPPLIER]
Note: Breng de info samen op basis van de eigenschap doeluuid
FeatureMerger_3
    ATTR_ACCUM_MODE = Merge Supplier
    ATTR_CONFLICT_RES = Use Requestor
    IGNORE_NULLS = No
    JOIN_KEYS = @Value(doeluuid) @Value(doeluuid) AUTO
    MERGE_TYPE = Attributes Only
    PROCESS_DUPS = NO
    REJECT_NULL_MISSING_KEYS = No
    SUPPLIERS_FIRST = No
    MERGED -> DuplicateFilter
    <REJECTED> -> Logger_2
DuplicateFilter
    INPUT_ORDERED_CHOICE = No
    KEYATTR = doeluuid ProefBoomToestand.conditiewaarde ProefBoomToestand.gebreken ProefBoomToestand.onderhoudstoestand ProefBoomToestand.plantwijzewaarde ProefBoomToestand.stamomtrek ProefBoomToestand.standplaatswaarde Controlefiche.verstuurdOp
    UNIQUE -> AttributeManager_4
Note: Opschonen attributen alvorens de informatie te mergen met de eigenlijke Asset (Boom)
AttributeManager_4
    ATTR_TABLE:
      REMOVE upload_body (varchar(200))
      REMOVE uuid_list (buffer)
      REMOVE _response_body (buffer)
      REMOVE _http_status_code (buffer)
      REMOVE json_type (buffer)
      REMOVE json_index (uint32)
      REMOVE bronuuid (varchar(200))
      RENAME_SET_VALUE doeluuid > uuid (varchar(200))
      REMOVE doeluuid.total_count (uint64)
      REMOVE @type (varchar(200))
      REMOVE @id (varchar(200))
    -> FeatureMerger_2 [SUPPLIER]
Junction_6
    -> Output (output)
Output (output)
Logger_2
    LOG_FEATURE = LOG_ONLY
    MAXCOORDS = 20
    MAXFEATS = 20
    MESSAGE = Feature is:
    SEVERITY = INFO

Bookmark: Toevoegen info: heeft de boom een controlefiche [boolean] ?
Note: Toevoegen informatie: / heeft de boom een controlefiche [boolean]?
FeatureMerger_2
    ATTR_ACCUM_MODE = Merge Supplier
    ATTR_CONFLICT_RES = Use Requestor
    IGNORE_NULLS = No
    JOIN_KEYS = @Value(uuid) @Value(uuid) AUTO
    MERGE_TYPE = Attributes Only
    PROCESS_DUPS = NO
    REJECT_NULL_MISSING_KEYS = No
    SUPPLIERS_FIRST = No
    MERGED -> AttributeCreator
    UNMERGED_REQUESTOR -> AttributeCreator_2
Note: heeftControlefiche = true
AttributeCreator
    ATTR_TABLE = SET_TO heeftControlefiche (varchar(4)) = true
    -> Junction_6
Note: heeftControlefiche = false
AttributeCreator_2
    ATTR_TABLE = SET_TO heeftControlefiche (varchar(5)) = false
    -> Junction_6
