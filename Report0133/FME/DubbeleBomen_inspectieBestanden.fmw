FME workspace DubbeleBomen_inspectieBestanden.fmw

Parameters:
- OUTPUT_FOLDER = C:\Users\DriesVerdoodtNordend\Downloads\output_20240925   # Select the output folder
- MAX_BUFFER_BOOM_BOOM = 1   # Link Boom en Boom: max. bufferafstand (meter)
- DestDataset_XLSXW_3 = $(OUTPUT_FOLDER)\_dubbele_bomen_samenvatting.xlsx   # Destination Microsoft Excel File
- SourceDataset_SHAPEFILE = C:\DATA\AWV\GRB\Refprv.shp   # Source Esri Shapefile(s)
- TIMESTAMP:   # Timestamp
      from datetime import datetime
      return datetime.now().strftime('%Y%m%d')
- COOKIE = _hjSessionUser_1413636=eyJpZCI6IjQ1OTRlODY3LTg5NmItNTk4Yy1hZGM0LWY1MDg2ZGQ3YmVkMCIsImNyZWF0ZWQiOjE3MTMyNjUwODM3MjksImV4aXN0aW5nIjp0cnVlfQ==; _ga=GA1.1.220652939.1712582701; vo-taalkeuze=NL; _ga_KK7F9Y5Z4P=GS1.1.1725608638.32.1.1725609028.0.0.0; _ga_GR51QK0425=GS1.1.1725892656.6.1.1725896180.0.0.0; _ga_G7W38XJN8R=GS1.1.1726067286.50.0.1726067286.0.0.0; VOGANONUSER=rB8dZGbzq94yAwAVgwGqAg==; acm-awv=820babc6eb334f1ba13201b2cdc51318; _ga_2XTMG0FZW0=GS1.1.1727245380.433.0.1727245380.0.0.0   # Cookie

Readers:
- SHAPEFILE_1: SHAPEFILE from $(SourceDataset_SHAPEFILE) in EPSG:31370
- XLSXR_1: XLSXR from $(FME_MF_DIR)DA-2024-24026_export.xlsx

Note: Dries Verdoodt / 13.09.2024 / Voorbereiding inspectiefiches van de dubbele bomen langs ieder wegsegment. / Schrijf een bestand voor ieder wegsegment (ident2). / Ieder bestand lijst alle bomen langsheen de weg in oplopende volgorde volgens de kilometerpaal referenties en de afstand tot deze kilometerpaal. / Iedere boom heeft en group.id indien ze gegroepeerd staan. Ontbreekt de groep id, dan staat die boom geïsoleerd (zoals het hoort). / De resultaten bevatten ook de info uit de controlefiche van de boom.
Note: Toekennen provincie waar de Boom staat. / Point: Boom / Area: provincie / ! Area first: yes (performance)
PointOnAreaOverlayer
    ATTR_ACCUM_MODE = Merge Incoming
    ATTR_CONFLICT_RES = Use Original
    DEAGGREGATE_INPUT = Yes
    POLYS_FIRST = YES
    POINT -> ModuloCounter
Note: PARALLEL PROCESSING: / Create random groups to perform parallel processing of the Custom Transformer ControleFiche
ModuloCounter
    CNT_ATTR = _modulo_count
    DOMAIN = modcounter
    MOD = 100
    -> ControleFiche
Note: Tot HIER
ControleFiche
    ASSETID.IDENTIFICATOR = @Value(assetId.identificator)
    COOKIE = $(COOKIE)
    -> AttributeRemover
Note: PARALLEL PROCESSING / _modulo_count
AttributeRemover
    REMOVE_ATTRS = _modulo_count
    -> TestFilter_2
    -> Junction_3
TestFilter_2
    DEFAULT_VALUE = ident2 ongekend
    PASSED_TEST_GROUP_OUTPUT = FIRST
    TEST_LIST = "BOOL_OP,OR,COMPOSITE_TEST,""""""1"""""",TEST_CLAUSE,TEST Weglocatie.ident2 ATTRIBUTE_HAS_A_VALUE """,ident2 gekend
    ident2 gekend -> NeighborFinder_3 [BASE]
    ident2 gekend -> NeighborFinder_3 [CANDIDATE]
    ident2 ongekend -> NeighborFinder_2 [CANDIDATE]
    ident2 ongekend -> NeighborFinder_2 [BASE]

Bookmark: [Excel] DAVIE Download
Note: Bomen / Vlaanderen / DAVIE-Conform
Boom (reader XLSXR_1)
    attributes: typeURI char(59), assetId.identificator char(56), aanleg string, aanleg.heeftBoomplaat string, aanleg.heeftWortelgeleidingwortelwering string, aanleg.plantmaatOmtrek string, aanleg.verankering string, aanleg.verankeringstype string, aanleg.vormAanlevering string, aanleg.wortelAanplant string, assetId.toegekendDoor char(3), boomspiegel[] char(16), datumOprichtingObject date, eindbeeld char(21), geschatteKlassePlantjaar char(9), groeifase char(13), heeftBoomrooster boolean, heeftLuchtleiding boolean, hoogte char(19), isActief boolean, isVerplant string, naam number(6,0), niveau number(4,1), notitie char(116), soortnaam.soortnaamNederlands char(52), soortnaam.soortnaamWetenschappelijk char(40), soortnaam.wetenschappelijkeSoortnaam char(36), takvrijeStamlengte number(3,1), toestand char(10), geometry char(37)
    -> TestFilter
TestFilter
    DEFAULT_VALUE = isActief False
    PASSED_TEST_GROUP_OUTPUT = FIRST
    TEST_LIST = "BOOL_OP,OR,COMPOSITE_TEST,""""""1"""""",TEST_CLAUSE,TEST @Value(isActief) = true",isActief True
    isActief True -> GeometryReplacer
HeeftBetrokkene (reader XLSXR_1) [off]
    attributes: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

Bookmark: Replace geometry
GeometryReplacer
    KIND_LONG = OGC Well Known Text
    OGC_WKT_PRECISION_DISPLAY = 64-bit
    REMOVE_ATTRIBUTE = No
    SOURCE = @Value(geometry)
    -> CoordinateSystemSetter
    <REJECTED> -> Junction_6
CoordinateSystemSetter
    COORDSYS = EPSG:31370
    -> PointOnAreaOverlayer [POINT]
Note: Boom zonder geometrie
Junction_6

Bookmark: [ESRI Shape] Provincies
Note: OPTIONEEL: / Toekennen provincie waarbinnen iedere boom ligt.
Refprv (reader SHAPEFILE_1)
    attributes: OIDN number(15,0), UIDN number(15,0), TERRID long, NAAM varchar(64), NISCODE varchar(5), NUTS2 varchar(10), LENGTE double, OPPERVL double
    -> AttributeRenamer
AttributeRenamer
    ATTR_TABLE = RENAME_SET_DEFAULT NAAM > provincie
    KEEP_RENAMED_ONLY = no
    MISSING_INPUT_ATTRS = REMOVE
    -> PointOnAreaOverlayer [AREA]

Bookmark: Toevoegen group.id
Note: Alle Bomen
Junction_3
    -> FeatureMerger [REQUESTOR]
Note: Base en Candidate input poort zijn identiek. / Group by: Weglocatie.ident2 / Alle elementen van een groep zitten zo in de lijst. / De attributen van de feature worden overbodig, want deze zit mee in de lijst.
NeighborFinder_3
    CANDIDATES_FIRST = No
    CLOSE_LIST_ATTRS_TO_INCLUDE = assetId.identificator Weglocatie.ident2 Weglocatie.ident8 Weglocatie.referentiepaalAfstand Weglocatie.referentiepaalOpschrift
    CLOSE_LIST_ATTRS_TO_INCLUDE_MODE = Selected Attributes
    CLOSE_LIST_NAME = DubbeleBoom
    GROUP_BY = Weglocatie.ident2
    INSERT_VERTEX = No
    MAX = $(MAX_BUFFER_BOOM_BOOM)
    MEASURES_FROM_CANDIDATE = Yes
    MEASURE_TYPE = Continuous
    MODE = Bases and Candidates
    TREAT_POLYGON_AS = Lines
    MATCHED -> ListElementCounter
ListElementCounter
    CNT_ATTR = _element_count
    LIST_NAME = DubbeleBoom{}
    -> TestFilter_3
TestFilter_3
    DEFAULT_VALUE = <UNFILTERED>
    PASSED_TEST_GROUP_OUTPUT = FIRST
    TEST_LIST = "BOOL_OP,OR,COMPOSITE_TEST,""""""1"""""",TEST_CLAUSE,TEST @Value(_element_count) >= 2",Dubbele boom
    Dubbele boom -> Counter_2
    <UNFILTERED> -> AttributeCreator
Note: Toekennen van een group.id, enkel voor de dubbele bomen. Voor alle records die uit minstens 2 lijst elementen bestaan.
Counter_2
    CNT_ATTR = group.id
    DOMAIN = counter
    SCOPE = Global
    START = 0
    -> ListExploder_4
ListExploder_4
    ATTR_ACCUM_MODE = Merge List Attributes
    ATTR_CONFLICT_RES = Use List Attribute Values
    INDEX_ATTR = _element_index
    LIST_ATTR = DubbeleBoom{}
    ELEMENTS -> AttributeKeeper_2
AttributeKeeper_2
    CREATE_BULK_MODE_FEATURES = NO
    KEEP_ATTRS = assetId.identificator,group.id,Weglocatie.ident2,Weglocatie.ident8,Weglocatie.referentiepaalAfstand,Weglocatie.referentiepaalOpschrift
    -> DuplicateFilter_2
Note: Behoud 1 unieke boom (assetId.identificator) per wegsegment (referentiepunt.Wegnummer) / Group by: / - assetId.identificator / - referentiepunt.Wegnummer
DuplicateFilter_2
    INPUT_ORDERED_CHOICE = No
    KEYATTR = assetId.identificator Weglocatie.ident2
    UNIQUE -> FeatureMerger [SUPPLIER]
Note: group.id = <null>
AttributeCreator
    ATTR_TABLE = SET_TO group.id (varchar(14)) = FME_NULL_VALUE
Note: Base en Candidate input poort zijn identiek. / Group by: referntiepunt.Wegnummer / Alle elementen van een groep zitten zo in de lijst. / De attributen van de feature worden overbodig, want deze zit mee in de lijst.
NeighborFinder_2
    CANDIDATES_FIRST = No
    CLOSE_LIST_ATTRS_TO_INCLUDE = assetId.identificator
    CLOSE_LIST_ATTRS_TO_INCLUDE_MODE = Selected Attributes
    CLOSE_LIST_NAME = DubbeleBoom
    INSERT_VERTEX = No
    MAX = $(MAX_BUFFER_BOOM_BOOM)
    MEASURES_FROM_CANDIDATE = Yes
    MEASURE_TYPE = Continuous
    MODE = Bases and Candidates
    TREAT_POLYGON_AS = Lines
    MATCHED -> ListElementCounter_2
ListElementCounter_2
    CNT_ATTR = _element_count
    LIST_NAME = DubbeleBoom{}
    -> TestFilter_4
TestFilter_4
    DEFAULT_VALUE = <UNFILTERED>
    PASSED_TEST_GROUP_OUTPUT = FIRST
    TEST_LIST = "BOOL_OP,OR,COMPOSITE_TEST,""""""1"""""",TEST_CLAUSE,TEST @Value(_element_count) >= 2",Dubbele boom
    Dubbele boom -> AttributeCreator_3
    <UNFILTERED> -> AttributeCreator_2
Note: group.id = -99
AttributeCreator_3
    ATTR_TABLE = SET_TO group.id (varchar(14)) = -99
    -> ListExploder_2
ListExploder_2
    ATTR_ACCUM_MODE = Merge List Attributes
    ATTR_CONFLICT_RES = Use List Attribute Values
    INDEX_ATTR = _element_index
    LIST_ATTR = DubbeleBoom{}
    ELEMENTS -> AttributeKeeper_3
AttributeKeeper_3
    CREATE_BULK_MODE_FEATURES = NO
    KEEP_ATTRS = assetId.identificator,group.id,Weglocatie.ident2,Weglocatie.ident8,Weglocatie.referentiepaalAfstand,Weglocatie.referentiepaalOpschrift
    -> DuplicateFilter_3
Note: Behoud 1 unieke boom (assetId.identificator) per wegsegment (referentiepunt.Wegnummer) / Group by: / - assetId.identificator / - referentiepunt.Wegnummer
DuplicateFilter_3
    INPUT_ORDERED_CHOICE = No
    KEYATTR = assetId.identificator Weglocatie.ident2
    UNIQUE -> FeatureMerger [SUPPLIER]
Note: Toevoegen group.id
FeatureMerger
    ATTR_ACCUM_MODE = Merge Supplier
    ATTR_CONFLICT_RES = Use Requestor
    IGNORE_NULLS = No
    JOIN_KEYS = @Value(assetId.identificator) @Value(assetId.identificator) AUTO
    MERGE_TYPE = Attributes Only
    PROCESS_DUPS = NO
    REJECT_NULL_MISSING_KEYS = No
    SUPPLIERS_FIRST = No
    MERGED -> AttributeManager
    UNMERGED_REQUESTOR -> AttributeManager
Note: group.id = <null>
AttributeCreator_2
    ATTR_TABLE = SET_TO group.id (varchar(14)) = FME_NULL_VALUE

Bookmark: Data preprocessing alvorens weg te schrijven
AttributeManager
    ATTR_TABLE:
      RENAME_SET_VALUE group.id > AWV.group.id (int64)
      SET_TO AWV.isActief.voorstel (varchar(200)) = @Value(isActief)
      RENAME_SET_VALUE heeftControlefiche > AWV.heeftControlefiche (varchar(4))
      REMOVE uuid (varchar(200))
    -> Sorter
Note: kilometerpalen / oplopend / referentiepunt.Opschrift / refernetiepunt.afstand / group.id
Sorter
    GROUP_BY = Weglocatie.ident2
    SORT_PARM = AWV.group.id NATURAL ASCENDING Weglocatie.referentiepaalOpschrift NATURAL ASCENDING Weglocatie.referentiepaalAfstand NATURAL ASCENDING
    SORTED -> StatisticsCalculator
    SORTED -> AttributeManager_3

Bookmark: File per wegsegment
Note: Create fanout attribute _filename
AttributeManager_3
    ATTR_TABLE = SET_TO _filename (varchar(200)) = @Value(Weglocatie.ident2)_dubbeleBoom_$(TIMESTAMP).xlsx
    -> FeatureWriter [Output]
FeatureWriter
    DATASET = $(OUTPUT_FOLDER)/@Value(_filename)
    DATASET_ATTR = _dataset
    FEATURE_TYPE_LIST_ATTR = _feature_types
    FORMAT = XLSXW
    TOTAL_FEATURES_WRITTEN_ATTR = _total_features_written
    XLSXW_COORDINATE_SYSTEM_GRANULARITY = FEATURE
    XLSXW_CUSTOM_NUMBER_FORMATTING = ENABLE_NATIVE
    XLSXW_DESTINATION_DATASETTYPE_VALIDATION = Yes
    XLSXW_DROP_TABLE = No
    XLSXW_FIELD_NAMES_FORMATTING = YES
    XLSXW_FIELD_NAMES_OUT = Yes
    XLSXW_INSERT_IGNORE_DB_OP = Yes
    XLSXW_MULTIPLE_TEMPLATE_SHEETS = Yes
    XLSXW_OVERWRITE_FILE = Yes
    XLSXW_PROTECT_SHEET = NO
    XLSXW_RASTER_FORMAT = PNG
    XLSXW_REMOVE_UNCHANGED_TEMPLATE_SHEET = No
    XLSXW_STRICT_SCHEMA_ADDITIONAL_ATTRIBUTE_MATCHING = yes
    XLSXW_TRUNCATE_TABLE = No
    XLSXW_WRITER_MODE = Insert

Bookmark: Samenvatting
StatisticsCalculator
    ATTR_ACCUM_MODE = None
    CALCULATION_MODE = NUMERIC
    FEAT_STATS = AWV.group.id,NUMERIC_MODE,,,COUNT,,,,NUMERIC,,,,,,
    GROUP_BY = Weglocatie.ident2
    SUMMARY -> AttributeManager_2
AttributeManager_2
    ATTR_TABLE:
      RENAME_SET_VALUE AWV.group.id.total_count > aantal.totaal (uint64)
      RENAME_SET_VALUE AWV.group.id.numeric_count > aantal.dubbels (uint64)
      SET_TO aantal.percentueel (real64) = @Evaluate(@round(@Value(aantal.dubbels)/@Value(aantal.totaal),0))
      SET_TO vaststelling (varchar(200))
      SET_TO oplossing (varchar(200))
      SET_TO opmerking (varchar(200))
    -> Sorter_3
Sorter_3
    SORT_PARM = Weglocatie.ident2 NATURAL ASCENDING
    SORTED -> FeatureWriter_2 [Output]
FeatureWriter_2
    DATASET = $(DestDataset_XLSXW_3)
    DATASET_ATTR = _dataset
    FEATURE_TYPE_LIST_ATTR = _feature_types
    FORMAT = XLSXW
    TOTAL_FEATURES_WRITTEN_ATTR = _total_features_written
    XLSXW_COORDINATE_SYSTEM_GRANULARITY = FEATURE
    XLSXW_CUSTOM_NUMBER_FORMATTING = ENABLE_NATIVE
    XLSXW_DESTINATION_DATASETTYPE_VALIDATION = Yes
    XLSXW_DROP_TABLE = No
    XLSXW_FIELD_NAMES_FORMATTING = NO
    XLSXW_FIELD_NAMES_OUT = Yes
    XLSXW_INSERT_IGNORE_DB_OP = Yes
    XLSXW_MULTIPLE_TEMPLATE_SHEETS = Yes
    XLSXW_OVERWRITE_FILE = Yes
    XLSXW_PROTECT_SHEET = NO
    XLSXW_RASTER_FORMAT = PNG
    XLSXW_REMOVE_UNCHANGED_TEMPLATE_SHEET = No
    XLSXW_STRICT_SCHEMA_ADDITIONAL_ATTRIBUTE_MATCHING = yes
    XLSXW_TRUNCATE_TABLE = No
    XLSXW_WRITER_MODE = Insert

Bookmark: [Excel]
Note: Fanout op basis van het wegsegment / Samenvatting van de aantallen per wegsegment

FME custom transformer ControleFiche
Toevoegen boolean attribuut "heeftControlefiche" voor iedere Boom o.b.v. een API-Call.

Parameters:
- ASSETID.IDENTIFICATOR = @Value(assetId.identificator)   # assetId.identificator
- COOKIE = _hjSessionUser_1413636=eyJpZCI6IjQ1OTRlODY3LTg5NmItNTk4Yy1hZGM0LWY1MDg2ZGQ3YmVkMCIsImNyZWF0ZWQiOjE3MTMyNjUwODM3MjksImV4aXN0aW5nIjp0cnVlfQ==; _ga=GA1.1.220652939.1712582701; vo-taalkeuze=NL; _ga_KK7F9Y5Z4P=GS1.1.1725608638.32.1.1725609028.0.0.0; _ga_GR51QK0425=GS1.1.1725892656.6.1.1725896180.0.0.0; _ga_G7W38XJN8R=GS1.1.1726067286.50.0.1726067286.0.0.0; VOGANONUSER=rB8dZGbqd/UyHwAabDlQAg==; acm-awv=97472f24145941358956b77fab54f2d1; _ga_2XTMG0FZW0=GS1.1.1726642387.413.1.1726642390.0.0.0   # Cookie
- FME_PROCESS_GROUP_BY =   # "" Group By
- FME_PROCESS_GROUPS_ORDERED = No   # When All Features Received,No%When Group Changes (Advanced),Yes Complete Groups

Input (input)
    -> Junction_5
Junction_5
    -> PythonCaller_3
    -> AttributeManager_5
AttributeManager_5
    ATTR_TABLE = SET_TO uuid (varchar(200)) = @Left(@Value(assetId.identificator), 36)
    -> FeatureMerger_2 [REQUESTOR]
Note: Groepeer de uuid's in een lijst van maximaal 100 assets. / Stuur iedere lijst van 100 assets naar de API request, zodat het aantal requests (verkeer) afneemt.
PythonCaller_3
    HIDE_ATTRIBUTES = assetId.identificator
    NEW_ATTRIBUTES = uuid_list buffer
    PYTHONSOURCE:
      import fme
      import fmeobjects


      class FeatureProcessor(object):
          """

          """

          def __init__(self):
              """
              """
              self.uuid_list = []


          def input(self, feature: fmeobjects.FMEFeature):
              """
              """
              uuid = feature.getAttribute('assetId.identificator')[:36]  # Slice the first 36 characters of the string
              self.uuid_list.append(uuid)

              #self.pyoutput(feature)

          def close(self):
              # Split into chunks of 1000 items
              chunks = [self.uuid_list[i:i + 100] for i in range(0, len(self.uuid_list), 100)]

              for chunk in chunks:
                  newFeature = fmeobjects.FMEFeature()
                  # Convert the list to a string, with elements separated by a comma and space
                  chunks_as_string = ', '.join(f'"{item}"' for item in chunk)
                  newFeature.setAttribute('uuid_list', chunks_as_string)
                  self.pyoutput(newFeature)
    PYTHONSYMBOL = FeatureProcessor
    -> AttributeCreator_5
Note: upload_body (payload)
AttributeCreator_5
    ATTR_TABLE:
      SET_TO upload_body (varchar(200)) = {
            "actiefFilter": true,
            "expandDepth": 1,
            "limit": 1000,
            "relatieTypesToExpand": [
                "e801b062-74e1-4b39-9401-163dd91d5494"
                ],
            "relatieTypesToReturn": [
                "e801b062-74e1-4b39-9401-163dd91d5494"
                ],
            "uuidsToExpand": [
                @Value(uuid_list)
            ],
            "uuidsToInclude": [
                @Value(uuid_list)
            ]
        }
    -> HTTPCaller
Note: API-Call: / Zoek alle assetsrelaties met als doeluuid een uuid van een boom met als relatietype "Bezoekt" / https://apps.mow.vlaanderen.be/eminfra/core/api/assets/graph / Copy the Cookie from a Browser
HTTPCaller
    CONNECTION_TIMEOUT_LENGTH = 60
    CUSTOM_HEADERS = Cookie;$(COOKIE)
    ERROR_ATTR = _error
    FOLLOW_REDIRECTS = FOLLOW_WITH_GET
    HTTP_METHOD = POST
    MAX_HTTP_VERSION = HTTP_2
    MAX_TRANSFERS_IN_PROGRESS = 25
    MINIMUM_ENCRYPTION_LEVEL = OS_DEFAULT
    REDIRECT_AUTH = ORIGINAL_DOMAIN_ONLY
    RESPONSE_TYPE = Attribute
    SPLIT_MULTIPART_DOWNLOADS = NO
    STATUS_CODE_ATTR = _http_status_code
    TARGET_ATTR = _response_body
    TARGET_ATTR_ENCODING = auto-detect
    TARGET_URL = https://apps.mow.vlaanderen.be/eminfra/core/api/assets/graph
    TRANSFER_TIMEOUT_LENGTH = 90
    UPLOAD_BODY = @Value(upload_body)
    UPLOAD_CONTENT_TYPE = JSON (application/json)
    UPLOAD_TYPE = Specify Upload Body
    USE_COOKIES = No
    VERIFY_SSL_CERTIFICATES = Yes
    -> JSONFragmenter_2
Note: Split the response in fragments (list) / Haal de "links" op tussen een boom en een controlefiche. / Splits op in fragmenten per / boom <-> controlefiche.
JSONFragmenter_2
    EXPLODE_FORMAT = JSON
    EXTRACT_ATTR = Yes
    JSON_ATTR = _response_body
    JSON_QUERY = json["links"][*]
    PREF_STRING = boom.links.
    READ_FROM_FILE = NO
    RECURSIVE = YES
    REJECT_EMPTY_LISTS = YES
    FRAGMENTS -> JSONExtractor
Note: bronuuid (ProefBoomToestand) / doeluuid (Boom)
JSONExtractor
    EXTRACT_QUERY_TABLE = bronuuid json["bronUuid"] doeluuid json["doelUuid"]
    JSON_DOCUMENT = @Value(_response_body)
    READ_FROM_FILE = NO
    EVALUATED -> PythonCaller_2
    EVALUATED -> PythonCaller_4
Note: Groepeer de uuid's in een lijst van maximaal 100 assets. / Stuur iedere lijst van 100 assets naar de API request, zodat het aantal requests (verkeer) afneemt.
PythonCaller_2 [off]
    NEW_ATTRIBUTES = uuid_list buffer
    PYTHONSOURCE:
      import fme
      import fmeobjects


      class FeatureProcessor(object):
          """

          """

          def __init__(self):
              """
              """
              self.uuid_list_bronuuid = []
              self.uuid_list_doeluuid = []


          def input(self, feature: fmeobjects.FMEFeature):
              """
              """
              bronuuid = feature.getAttribute('bronuuid')
              self.uuid_list_bronuuid.append(bronuuid)
              doeluuid = feature.getAttribute('doeluuid')
              self.uuid_list_doeluuid.append(doeluuid)


              #self.pyoutput(feature)

          def close(self):
              # Split into chunks of 100 items
              chunks_bronuuid = [self.uuid_list_bronuuid[i:i + 100] for i in range(0, len(self.uuid_list_bronuuid), 100)]
              chunks_doeluuid = [self.uuid_list_doeluuid[i:i + 100] for i in range(0, len(self.uuid_list_doeluuid), 100)]

              for chunk in chunks:
                  newFeature = fmeobjects.FMEFeature()
                  # Convert the list to a string, with elements separated by a comma and space
                  chunks_as_string = ', '.join(f'"{item}"' for item in chunk)
                  newFeature.setAttribute('uuid_list', chunks_as_string)
                  self.pyoutput(newFeature)
    PYTHONSYMBOL = FeatureProcessor
    -> HTTPCaller_3
PythonCaller_4
    NEW_ATTRIBUTES = _group buffer
    PYTHONSOURCE:
      import fme
      import fmeobjects


      class FeatureProcessor(object):
          """
          Maak een counter die per 100 features een unieke ID toekent.
          """

          def __init__(self):
              """
              """
              self.feature_counter = 0
              self.group_counter = 1


          def input(self, feature: fmeobjects.FMEFeature):
              """
              """
              # increase the feature counter
              self.feature_counter += 1

              if self.feature_counter <= 100:
                  pass
              else:
                  # augment the group counter
                  self.group_counter += 1
                  # reset the feature counter
                  self.feature_counter = 0

              # Set group_counter
              feature.setAttribute('_group', self.group_counter)

              # Wrap  double quotes around bronuuid and doeluuid
              bronuuid = f'"{feature.getAttribute('bronuuid')}"'
              doeluuid = f'"{feature.getAttribute('doeluuid')}"'

              feature.setAttribute('bronuuid', bronuuid)
              feature.setAttribute('doeluuid', doeluuid)


              self.pyoutput(feature)

          def close(self):
              pass
    PYTHONSYMBOL = FeatureProcessor
    -> Aggregator
Aggregator
    ACCUM_ATTRS_NAME = Merge Incoming Attributes
    AGGREGATE_TYPE = Homogeneous Collection (If Possible)
    CONCAT_ATTRS = bronuuid doeluuid
    GROUP_BY = _group
    MODE = Geometry - Assemble One Level
    SEP = ", "
    AGGREGATE -> HTTPCaller_3
Note: Haal de ControleFiches op van de boom / POST / https://apps.mow.vlaanderen.be/eminfra/core/api/otl/controlefiches/search
HTTPCaller_3
    CONNECTION_TIMEOUT_LENGTH = 60
    CUSTOM_HEADERS = Cookie;$(COOKIE)
    ERROR_ATTR = _error
    FOLLOW_REDIRECTS = FOLLOW_WITH_GET
    HTTP_METHOD = POST
    MAX_HTTP_VERSION = HTTP_2
    MAX_TRANSFERS_IN_PROGRESS = 25
    MINIMUM_ENCRYPTION_LEVEL = OS_DEFAULT
    REDIRECT_AUTH = ORIGINAL_DOMAIN_ONLY
    RESPONSE_TYPE = Attribute
    SPLIT_MULTIPART_DOWNLOADS = NO
    STATUS_CODE_ATTR = _http_status_code
    TARGET_ATTR = _response_body
    TARGET_ATTR_ENCODING = auto-detect
    TARGET_URL = https://apps.mow.vlaanderen.be/eminfra/core/api/otl/controlefiches/search
    TRANSFER_TIMEOUT_LENGTH = 90
    UPLOAD_BODY:
      {
        "size": 1000,
        "filters": {
          "uuid": [
          @Value(bronuuid)
          ]
        }
      }
    UPLOAD_CONTENT_TYPE = JSON (application/json)
    UPLOAD_TYPE = Specify Upload Body
    USE_COOKIES = No
    VERIFY_SSL_CERTIFICATES = Yes
    -> JSONFragmenter_3
Note: Splits het antwoord op in verschillende JSON fragmenten.
JSONFragmenter_3
    EXPLODE_FORMAT = JSON
    EXTRACT_ATTR = No
    JSON_ATTR = _response_body
    JSON_QUERY = json["@graph"][*]
    READ_FROM_FILE = NO
    REJECT_EMPTY_LISTS = YES
    FRAGMENTS -> JSONExtractor_4
Note: Algemeen / @type / @id
JSONExtractor_4
    EXTRACT_QUERY_TABLE = @type json["@type"] @id json["@id"]
    JSON_DOCUMENT = @Value(_response_body)
    READ_FROM_FILE = NO
    EVALUATED -> AttributeFilter
Note: Sommige delen van het antwoord van de API-call interesseren ons niet.
AttributeFilter
    ATTR_NAME = @type
    ATTR_VALUES = <Empty>,<Missing>,<Null>,<Unfiltered>,https://bz.data.wegenenverkeer.be/ns/aanleiding#Proef,https://bz.data.wegenenverkeer.be/ns/beheeractie#ProefBoomToestand,https://bz.data.wegenenverkeer.be/ns/controlefiche#ProefBoomToestand,https://bz.data.wegenenverkeer.be/ns/onderdeel#Bezoekt,https://bz.data.wegenenverkeer.be/ns/onderdeel#HeeftBeheeractie,https://bz.data.wegenenverkeer.be/ns/onderdeel#IsAanleiding,https://wegenenverkeer.data.vlaanderen.be/ns/onderdeel#Boom
    https://bz.data.wegenenverkeer.be/ns/beheeractie#ProefBoomToestand -> JSONExtractor_2
    https://bz.data.wegenenverkeer.be/ns/controlefiche#ProefBoomToestand -> JSONExtractor_3
    https://wegenenverkeer.data.vlaanderen.be/ns/onderdeel#Boom -> JSONExtractor_5
Note: onderdeel#Boom / Extraheer de afgeleide weglocatie: / ident2 / ident8 / referentiepaalOpschrift / referentiepaalAfstand
JSONExtractor_5
    EXTRACT_QUERY_TABLE = Weglocatie.ident2 json["loc:Locatie.puntlocatie"]["loc:DtcPuntlocatie.weglocatie"]["loc:DtcWeglocatie.ident2"] Weglocatie.ident8 json["loc:Locatie.puntlocatie"]["loc:DtcPuntlocatie.weglocatie"]["loc:DtcWeglocatie.ident8"] Weglocatie.referentiepaalOpschrift json["loc:Locatie.puntlocatie"]["loc:DtcPuntlocatie.weglocatie"]["loc:DtcWeglocatie.referentiepaalOpschrift"] Weglocatie.referentiepaalAfstand json["loc:Locatie.puntlocatie"]["loc:DtcPuntlocatie.weglocatie"]["loc:DtcWeglocatie.referentiepaalAfstand"]
    JSON_DOCUMENT = @Value(_response_body)
    READ_FROM_FILE = NO
    EVALUATED -> AttributeKeeper
AttributeKeeper
    CREATE_BULK_MODE_FEATURES = NO
    KEEP_ATTRS = Weglocatie.ident2,Weglocatie.ident8,Weglocatie.referentiepaalAfstand,Weglocatie.referentiepaalOpschrift,doeluuid
    -> FeatureMerger [REQUESTOR]
Note: Indien er 2 controlefiches zijn, hebben deze dezelfde waarde. Ze zijn 2 aan 2 gelijk.
Note: beheeractie#ProefBoomToestand
JSONExtractor_2
    EXTRACT_QUERY_TABLE = ProefBoomToestand.conditiewaarde json["bz:ProefBoomToestand.conditiewaarde"] ProefBoomToestand.conflicten json["bz:ProefBoomToestand.conflicten"] ProefBoomToestand.gebreken json["bz:ProefBoomToestand.gebreken"] ProefBoomToestand.onderhoudstoestand json["bz:ProefBoomToestand.onderhoudstoestand"] ProefBoomToestand.plantwijzewaarde json["bz:ProefBoomToestand.plantwijzewaarde"] ProefBoomToestand.stamomtrek json["bz:ProefBoomToestand.stamomtrek"] ProefBoomToestand.standplaatswaarde json["bz:ProefBoomToestand.standplaatswaarde"] ProefBoomToestand.kroonDiameter json["bz:ProefBoomToestand.kroonDiameter"] ProefBoomToestand.meerwaarde json["bz:ProefBoomToestand.meerwaarde"]
    JSON_DOCUMENT = @Value(_response_body)
    READ_FROM_FILE = NO
    EVALUATED -> PythonCaller
Note: Format attributes
PythonCaller
    HIDE_ATTRIBUTES = @id @type _http_status_code _response_body bronuuid json_index json_type upload_body uuid_list
    PYTHONSOURCE:
      import fme
      import fmeobjects


      class FeatureProcessor(object):
          """

          """

          def __init__(self):
              """
              """
              pass

          def input(self, feature: fmeobjects.FMEFeature):
              """
              """
              conflicten = feature.getAttribute('ProefBoomToestand.conflicten')
              conflicten_formatted = ';'.join([i.split('/')[-1] for i in conflicten])  # Concatenate list elements and omit the URL before the last forward-slash
              feature.setAttribute('ProefBoomToestand.conflicten', conflicten_formatted)

              conditiewaarde = feature.getAttribute('ProefBoomToestand.conditiewaarde')
              conditiewaarde_formatted = conditiewaarde.split('/')[-1]
              feature.setAttribute('ProefBoomToestand.conditiewaarde', conditiewaarde_formatted)

              gebreken = feature.getAttribute('ProefBoomToestand.gebreken')
              gebreken_formatted = ';'.join([i.split('/')[-1] for i in gebreken])  # Concatenate list elements and omit the URL before the last forward-slash
              feature.setAttribute('ProefBoomToestand.gebreken', gebreken_formatted)

              onderhoudstoestand = feature.getAttribute('ProefBoomToestand.onderhoudstoestand')
              onderhoudstoestand_formatted = onderhoudstoestand.split('/')[-1]
              feature.setAttribute('ProefBoomToestand.onderhoudstoestand', onderhoudstoestand_formatted)

              meerwaarde = feature.getAttribute('ProefBoomToestand.meerwaarde')
              meerwaarde_formatted = ';'.join([i.split('/')[-1] for i in meerwaarde])  # Concatenate list elements and omit the URL before the last forward-slash
              feature.setAttribute('ProefBoomToestand.meerwaarde', meerwaarde_formatted)

              plantwijzewaarde = feature.getAttribute('ProefBoomToestand.plantwijzewaarde')
              plantwijzewaarde_formatted = plantwijzewaarde.split('/')[-1]
              feature.setAttribute('ProefBoomToestand.plantwijzewaarde', plantwijzewaarde_formatted)

              standplaatswaarde = feature.getAttribute('ProefBoomToestand.standplaatswaarde')
              standplaatswaarde_formatted = standplaatswaarde.split('/')[-1]
              feature.setAttribute('ProefBoomToestand.standplaatswaarde', standplaatswaarde_formatted)

              self.pyoutput(feature)

          def close(self):
              pass
    PYTHONSYMBOL = FeatureProcessor
    -> FeatureMerger [SUPPLIER]
Note: Breng de info samen op basis van de eigenschap doeluuid
FeatureMerger
    ATTR_ACCUM_MODE = Merge Supplier
    ATTR_CONFLICT_RES = Use Requestor
    IGNORE_NULLS = No
    JOIN_KEYS = @Value(doeluuid) @Value(doeluuid) AUTO
    MERGE_TYPE = Attributes Only
    PROCESS_DUPS = NO
    REJECT_NULL_MISSING_KEYS = No
    SUPPLIERS_FIRST = No
    MERGED -> FeatureMerger_3 [REQUESTOR]
    <REJECTED> -> Logger
Logger
    LOG_FEATURE = LOG_ONLY
    MAXCOORDS = 20
    MAXFEATS = 20
    MESSAGE = Feature is:
    SEVERITY = INFO
Note: Indien er 2 controlefiches zijn, heeft de eigenschap "verstuurd op" voor de eerste record een waarde en voor de tweede record geen waarde. / De eerste record wordt gebruikt en de lege eigenschap genegeerd.
Note: controlefiche#ProefBoomToestand
JSONExtractor_3
    EXTRACT_QUERY_TABLE = Controlefiche.verstuurdOp json["bz:Controlefiche.verstuurdOp"]
    JSON_DOCUMENT = @Value(_response_body)
    READ_FROM_FILE = NO
    EVALUATED -> AttributeKeeper_2
AttributeKeeper_2
    CREATE_BULK_MODE_FEATURES = NO
    KEEP_ATTRS = doeluuid,Controlefiche.verstuurdOp
    -> FeatureMerger_3 [SUPPLIER]
Note: Breng de info samen op basis van de eigenschap doeluuid
FeatureMerger_3
    ATTR_ACCUM_MODE = Merge Supplier
    ATTR_CONFLICT_RES = Use Requestor
    IGNORE_NULLS = No
    JOIN_KEYS = @Value(doeluuid) @Value(doeluuid) AUTO
    MERGE_TYPE = Attributes Only
    PROCESS_DUPS = NO
    REJECT_NULL_MISSING_KEYS = No
    SUPPLIERS_FIRST = No
    MERGED -> DuplicateFilter
    <REJECTED> -> Logger_2
DuplicateFilter
    INPUT_ORDERED_CHOICE = No
    KEYATTR = doeluuid ProefBoomToestand.conditiewaarde ProefBoomToestand.gebreken ProefBoomToestand.onderhoudstoestand ProefBoomToestand.plantwijzewaarde ProefBoomToestand.stamomtrek ProefBoomToestand.standplaatswaarde Controlefiche.verstuurdOp
    UNIQUE -> StringReplacer
Note: Verwijder dubbele aanhalingstekens rond doeluuid
StringReplacer
    CASE = NO
    FIND_TEXT = "
    NO_MATCH = _FME_NO_OP_
    REGEXP = NO
    SRC_ATTRS = doeluuid
    -> AttributeManager_4
Note: Opschonen attributen alvorens de informatie te mergen met de eigenlijke Asset (Boom)
AttributeManager_4
    ATTR_TABLE:
      RENAME_SET_VALUE doeluuid > uuid (varchar(200))
      RENAME_SET_VALUE Controlefiche.verstuurdOp > ProefBoomToestand.verstuurdOp (varchar(200))
    -> FeatureMerger_2 [SUPPLIER]
Junction_6
    -> Output (output)
Output (output)
Logger_2
    LOG_FEATURE = LOG_ONLY
    MAXCOORDS = 20
    MAXFEATS = 20
    MESSAGE = Feature is:
    SEVERITY = INFO

Bookmark: Toevoegen info: heeft de boom een controlefiche [boolean] ?
Note: Toevoegen informatie: / heeft de boom een controlefiche [boolean]?
FeatureMerger_2
    ATTR_ACCUM_MODE = Merge Supplier
    ATTR_CONFLICT_RES = Use Requestor
    IGNORE_NULLS = No
    JOIN_KEYS = @Value(uuid) @Value(uuid) AUTO
    MERGE_TYPE = Attributes Only
    PROCESS_DUPS = NO
    REJECT_NULL_MISSING_KEYS = No
    SUPPLIERS_FIRST = No
    MERGED -> AttributeCreator
    UNMERGED_REQUESTOR -> AttributeCreator_2
Note: heeftControlefiche = true
AttributeCreator
    ATTR_TABLE = SET_TO heeftControlefiche (varchar(4)) = true
    -> Junction_6
Note: heeftControlefiche = false
AttributeCreator_2
    ATTR_TABLE = SET_TO heeftControlefiche (varchar(5)) = false
    -> Junction_6
